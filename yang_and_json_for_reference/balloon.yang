module balloon {

  yang-version "1.1";

	namespace "http://example.com/example-1";

  prefix "bal1";

  container readings {

    leaf txpower {
      type uint8;
    }
    
    leaf datarate {
      type uint8;
    }

    leaf temp_value {
      type int16;
    }

  }

}
